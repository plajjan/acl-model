module example-ext-route-filter {
  namespace "urn:ietf:params:xml:ns:yang:example-ext-route-filter";
  prefix example-ext-route-filter;

  import ietf-inet-types {
    prefix "inet";
  }
  import ietf-access-control-list {
    prefix "ietf-acl";
  }

  organization
    "Route model group.";

  contact
    "abc@abc.com";

  description "
    This module describes route filter as a collection of
    match prefixes. When specifying a match prefix, you
    can specify an exact match with a particular route or
    a less precise match. You can configure either a
    common action that applies to the entire list or an
    action associated with each prefix.
    ";
  revision YYYY-MM-DD {
    description
      "Creating Route-Filter extension model based on
      ietf-access-control-list model";
    reference "Example route filter";
  }

  augment "/ietf-acl:access-lists/ietf-acl:acl/" +
          "ietf-acl:aces/ietf-acl:ace/ietf-acl:matches" {
    description "
      This module augments the matches container in the ietf-acl
      module with route filter specific actions";

    choice route-prefix{
      description "Define route filter match criteria";
      case range {
        description
          "Route falls between the lower prefix/prefix-length
           and the upperprefix/prefix-length.";
        choice ipv4-range {
          description "Defines the IPv4 prefix range";
          leaf v4-lower-bound {
            type inet:ipv4-prefix;
            description
              "Defines the lower IPv4 prefix/prefix length";
          }
          leaf v4-upper-bound {
            type inet:ipv4-prefix;
            description
              "Defines the upper IPv4 prefix/prefix length";
          }
        }
        choice ipv6-range {
          description "Defines the IPv6 prefix/prefix range";
          leaf v6-lower-bound {
            type inet:ipv6-prefix;
            description
              "Defines the lower IPv6 prefix/prefix length";
          }
          leaf v6-upper-bound {
            type inet:ipv6-prefix;
            description
              "Defines the upper IPv6 prefix/prefix length";
          }
        }
      }
    }
  }
}
